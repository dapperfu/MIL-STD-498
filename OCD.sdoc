[DOCUMENT]
TITLE: OCD - Operational Concept Description.

[SECTION]
TITLE: Scope.

[FREETEXT]
This section shall be divided into the following paragraphs.
[/FREETEXT]

[SECTION]
TITLE: Identification.

[FREETEXT]
This paragraph shall contain a full identification of the system to which this document applies, including, as applicable, identification number(s), title(s), abbreviation(s), version number(s), and release number(s).
[/FREETEXT]

[/SECTION]

[SECTION]
TITLE: System overview.

[FREETEXT]
This paragraph shall briefly state the purpose of the system to which this document applies. It shall describe the general nature of the system; summarize the history of system development, operation, and maintenance; identify the project sponsor, acquirer, user, developer, and support agencies; identify current and planned operating sites; and list other relevant documents.
[/FREETEXT]

[/SECTION]

[SECTION]
TITLE: Document overview.

[FREETEXT]
This paragraph shall summarize the purpose and contents of this document and shall describe any security or privacy considerations associated with its use.
[/FREETEXT]

[/SECTION]

[/SECTION]

[SECTION]
TITLE: Referenced documents.

[FREETEXT]
This section shall list the number, title, revision, and date of all documents referenced in this document. This section shall also identify the source for all documents not available through normal Government stocking activities.
[/FREETEXT]

[/SECTION]

[SECTION]
TITLE: Current system or situation.

[FREETEXT]
This section shall be divided into the following paragraphs to describe the system or situation as it currently exists.
[/FREETEXT]

[SECTION]
TITLE: Background, objectives, and scope.

[FREETEXT]
This paragraph shall describe the background, mission or objectives, and scope of the current system or situation.
[/FREETEXT]

[/SECTION]

[SECTION]
TITLE: Operational policies and constraints.

[FREETEXT]
This paragraph shall describe any operational policies and constraints that apply to the current system or situation.
[/FREETEXT]

[/SECTION]

[SECTION]
TITLE: Description of current system or situation.

[FREETEXT]
This paragraph shall provide a description of the current system or situation, identifying differences associated with different states or modes of operation (for example, regular, mainte-nance, training, degraded, emergency, alternative-site, wartime, peacetime). The distinction between states and modes is arbitrary. A system may be described in terms of states only, modes only, states within modes, modes within states, or any other scheme that is useful. If the system operates without states or modes, this paragraph shall so state, without the need to create artificial distinctions. The description shall include, as applicable:

- The operational environment and its characteristics
- Major system components and the interconnections among these components
- Interfaces to external systems or procedures
- Capabilities/functions of the current system
- Charts and accompanying descriptions depicting inputs, outputs, data flow, and manual and automated processes sufficient to understand the current system or situation from the user's point of view
- Performance characteristics, such as speed, throughput, volume, frequency
- Quality attributes, such as reliability, maintainability, availability, flexibility, portability, usability, efficiency
- Provisions for safety, security, privacy, and continuity of operations in emergencies
[/FREETEXT]

[/SECTION]

[SECTION]
TITLE: Users or involved personnel.

[FREETEXT]
This paragraph shall describe the types of users of the system, or personnel involved in the current situation, including, as applicable, organizational structures, training/skills, responsibilities, activities, and interactions with one another.
[/FREETEXT]

[/SECTION]

[SECTION]
TITLE: Support concept.

[FREETEXT]
This paragraph shall provide an overview of the support concept for the current system, including, as applicable to this document, support agency(ies); facilities; equipment; support software; repair/replacement criteria; maintenance levels and cycles; and storage, distribution, and supply methods.
[/FREETEXT]

[/SECTION]

[/SECTION]

[SECTION]
TITLE: Justification for and nature of changes.

[FREETEXT]
This section shall be divided into the following paragraphs.
[/FREETEXT]

[SECTION]
TITLE: Support concept.

[FREETEXT]
This paragraph shall provide an overview of the support concept for the current system, including, as applicable to this document, support agency(ies); facilities; equipment; support software; repair/replacement criteria; maintenance levels and cycles; and storage, distribution, and supply methods.
[/FREETEXT]

[/SECTION]

[SECTION]
TITLE: Justification for and nature of changes.

[FREETEXT]
This section shall be divided into the following paragraphs.
[/FREETEXT]

[/SECTION]

[SECTION]
TITLE: Justification for change.

[FREETEXT]
This paragraph shall:

Describe new or modified aspects of user needs, threats, missions, objectives, environ-ments, interfaces, personnel or other factors that require a new or modified system.  
Summarize deficiencies or limitations in the current system or situation that make it unable to respond to these factors
[/FREETEXT]

[/SECTION]

[SECTION]
TITLE: Description of needed changes.

[FREETEXT]
This paragraph shall summarize new or modified capabilities/functions, processes, interfaces, or other changes needed to respond to the factors identified in 4.1.
[/FREETEXT]

[/SECTION]

[SECTION]
TITLE: Priorities among the changes.

[FREETEXT]
This paragraph shall identify priorities among the needed changes. It shall, for example, identify each change as essential, desirable, or optional, and prioritize the desirable and optional changes.
[/FREETEXT]

[/SECTION]

[/SECTION]
